ICOMM-LCP-MIB DEFINITIONS ::= BEGIN

IMPORTS
    MODULE-IDENTITY, OBJECT-TYPE, Integer32, Counter32, Counter64, Unsigned32, IpAddress, mib-2, enterprises       FROM SNMPv2-SMI
    MODULE-COMPLIANCE, OBJECT-GROUP                                                                                FROM SNMPv2-CONF
    TimeTicks                                                                                                      FROM RFC1155-SMI
    DisplayString, TestAndIncr, TimeStamp                                                                          FROM SNMPv2-TC
    InetAddress, InetAddressType, InetPortNumber                                                                   FROM INET-ADDRESS-MIB;

-- the path to the root

lcp MODULE-IDENTITY
	LAST-UPDATED "202210040000Z"
	ORGANIZATION "ICOMM Tele Limited."
	CONTACT-INFO "C.Srinvas.Rao, VP (R&D)
				  mail: srinivasaraoc@icommtele.com
	              Website: www.icommtele.com."
	DESCRIPTION "This MIB module is for the HCRR Lite Radio  of ICOMM Tele Limited, Hyderabad, India."
	REVISION "0601281300Z"
	DESCRIPTION "Started Development on Oct 04 2022, R&D, ICOMM Tele Limited - Hydeabad."
	::= { enterprises 21025 }

-- Configuration Information
radio                           OBJECT IDENTIFIER ::= { lcp 4 }
lcpInstallation        		OBJECT IDENTIFIER ::= { radio 1 }
lcpSlotconfiguration      	OBJECT IDENTIFIER ::= { radio 2 }
lcpFHconfig	       		OBJECT IDENTIFIER ::= { radio 3 }
lcpStatus	       		OBJECT IDENTIFIER ::= { radio 4 }
lcpcalbration	       		OBJECT IDENTIFIER ::= { radio 5 }
lcpIpAddrConfigure     		OBJECT IDENTIFIER ::= { radio 6 }
lcpTraps               		OBJECT IDENTIFIER ::= { radio 7 }


-- Variables under lcpInstallation

terminalMode OBJECT-TYPE
--OID .1.3.6.1.4.1.21025.4.1.1.0
    SYNTAX     Integer32
    MAX-ACCESS read-only
    STATUS     current
    DESCRIPTION
            " Radio Mode Base/Remote"
    ::= { lcpInstallation 1}

****//Base-1/Remote-2//Repeater-3//
-- Variables under lcpSlotconfiguration

SlotwiseTable OBJECT-TYPE
--OID .1.3.6.1.4.1.21025.4.2.2.0
    SYNTAX      SEQUENCE OF SlotconfigurationTableEntry
    MAX-ACCESS read-only
    STATUS      current
    DESCRIPTION
	"Slot configuration Table"
    ::= {  lcpSlotconfiguration 2 }

SlotconfigurationTable OBJECT-TYPE
--OID .1.3.6.1.4.1.21025.4.2.2.1.0
    SYNTAX      SEQUENCE OF SlotconfigurationTableEntry
    MAX-ACCESS read-only
    STATUS      current
    DESCRIPTION
	"Slot configuration Table"
    ::= {  SlotwiseTable 1 }

SlotconfigurationTableEntry OBJECT-TYPE
--OID .1.3.6.1.4.1.21025.4.2.2.1.1
    SYNTAX      SlotconfigurationTableEntry
    MAX-ACCESS read-only
    STATUS      current
    DESCRIPTION
        "Slot configuration Table Entry"
    INDEX   { slotActivate,fec,txpwr,channelno,remoteid,updownlink,indexslot }
    ::= { SlotconfigurationTable 1 }

SlotconfigurationTableEntry ::= SEQUENCE 
{
    slotActivate        Integer32,
    fec         	Integer32,
    txpwr        	Integer32,
    channelno         	Integer32,
    remoteid         	Integer32,
    updownlink        	Integer32,
    indexslot         	Integer32
}

slotActivate OBJECT-TYPE
--OID .1.3.6.1.4.1.21025.4.2.2.1.1.1	
    SYNTAX      Integer32
    MAX-ACCESS  read-only
    STATUS      current
    DESCRIPTION
        "SlotActivate "
    ::= { SlotconfigurationTableEntry 1 }

//0-Inactive & 1- Active

fec OBJECT-TYPE
--OID .1.3.6.1.4.1.21025.4.2.2.1.1.2	
    SYNTAX      Integer32
    MAX-ACCESS  read-only
    STATUS      current
    DESCRIPTION
        "FEC"
    ::= { SlotconfigurationTableEntry 2 }

//FEC ON-1/FEC OFF -0****

txpwr OBJECT-TYPE
--OID .1.3.6.1.4.1.21025.4.2.2.1.1.3	
    SYNTAX      Integer32
    MAX-ACCESS  read-only
    STATUS      current
    DESCRIPTION
        "TX Power"
    ::= { SlotconfigurationTableEntry 3 }

//range 15-36 display and config in between 15-36//

channelno OBJECT-TYPE
--OID .1.3.6.1.4.1.21025.4.2.2.1.1.4	
    SYNTAX      Integer32
    MAX-ACCESS  read-only
    STATUS      current
    DESCRIPTION
        "Frequency Mode and channel No"
    ::= { SlotconfigurationTableEntry 4 }

//range 1-302 display and config in between 1-302//

remoteid OBJECT-TYPE
--OID .1.3.6.1.4.1.21025.4.2.2.1.1.5	
    SYNTAX      Integer32
    MAX-ACCESS  read-only
    STATUS      current
    DESCRIPTION
        "Remote terminal No"
    ::= { SlotconfigurationTableEntry 5 }

//In between R1 to R6//

updownlink OBJECT-TYPE
--OID .1.3.6.1.4.1.21025.4.2.2.1.1.6	
    SYNTAX      Integer32
    MAX-ACCESS  read-only
    STATUS      current
    DESCRIPTION
        "UP link or Down Link"
    ::= { SlotconfigurationTableEntry 6 }

//UP link=1 or Down Link=2//

indexslot OBJECT-TYPE
--OID .1.3.6.1.4.1.21025.4.2.2.1.1.7	
    SYNTAX      Integer32
    MAX-ACCESS  read-only
    STATUS      current
    DESCRIPTION
        "index of slot configuration Table"
    ::= { SlotconfigurationTableEntry 7 }

//index of slot (1-6)

-- Variables under lcpStatus
Sysvoltages OBJECT-TYPE
--OID .1.3.6.1.4.1.21025.4.4.8.0
    SYNTAX     Integer32
    MAX-ACCESS read-only
    STATUS     current
    DESCRIPTION
            " Voltage 5v"
    ::= { lcpStatus 8}

voltage5VA OBJECT-TYPE
--OID .1.3.6.1.4.1.21025.4.4.8.1.0
    SYNTAX     Integer32
    MAX-ACCESS read-only
    STATUS     current
    DESCRIPTION
            " Voltage 5v"
    ::= { Sysvoltages 1}

//range in between 0 to +5v

voltage30v OBJECT-TYPE
--OID .1.3.6.1.4.1.21025.4.4.8.3.0
    SYNTAX     Integer32
    MAX-ACCESS read-only
    STATUS     current
    DESCRIPTION
            " Voltages 30v"
    ::= { Sysvoltages 3}

//range in between 0 to +30v

voltageneg5v OBJECT-TYPE
--OID .1.3.6.1.4.1.21025.4.4.8.5.0
    SYNTAX     Integer32
    MAX-ACCESS read-only
    STATUS     current
    DESCRIPTION
            " Voltage neg5v"
    ::= { Sysvoltages 5}

//range in between 0 to neg5v

voltage49v OBJECT-TYPE
--OID .1.3.6.1.4.1.21025.4.4.8.7.0
    SYNTAX     Integer32
    MAX-ACCESS read-only
    STATUS     current
    DESCRIPTION
            " Voltage pos49V"
    ::= { Sysvoltages 7}

//range in between 0 to 49v

SlotwiseHealthTable OBJECT-TYPE
--OID .1.3.6.1.4.1.21025.4.4.9.0
    SYNTAX      SEQUENCE OF SlotwiseHealthTableEntry
    MAX-ACCESS read-only
    STATUS      current
    DESCRIPTION
	"Slot configuration Table"
    ::= {  lcpStatus 9 }
//no 
SlotwiseHealthTableEntry OBJECT-TYPE
--OID .1.3.6.1.4.1.21025.4.4.9.1
    SYNTAX      SlotwiseHealthTableEntry
    MAX-ACCESS read-only
    STATUS      current
    DESCRIPTION
        "Slot configuration Table Entry"
    INDEX   { txpwrslot,rssislot,syncLoss,snr,indexhealth }
    ::= { SlotwiseHealthTable 1 }

SlotwiseHealthTableEntry ::= SEQUENCE 
{
    txpwrslot        	Integer32,//15-36
    rssislot         	Integer32,//30-90
    syncLoss        	Integer32,//0-fail/1-OK
    snr         	Integer32,//15-27
    indexhealth         Integer32//1-6
}

txpwrslot OBJECT-TYPE
--OID .1.3.6.1.4.1.21025.4.4.9.1.1	
    SYNTAX      Integer32
    MAX-ACCESS  read-only
    STATUS      current
    DESCRIPTION
        "txpwr of each slot "
    ::= { SlotwiseHealthTableEntry 1 }
//Range 15-36//

rssislot OBJECT-TYPE
--OID .1.3.6.1.4.1.21025.4.4.9.1.2
    SYNTAX      Integer32
    MAX-ACCESS  read-only
    STATUS      current
    DESCRIPTION
        "RSSI of each slot"
    ::= { SlotwiseHealthTableEntry 2 }

//In between 30- 90 will display.

syncLoss OBJECT-TYPE
--OID .1.3.6.1.4.1.21025.4.4.9.1.3	
    SYNTAX      Integer32
    MAX-ACCESS  read-only
    STATUS      current
    DESCRIPTION
        "sync status OKAY or FAIL"
    ::= { SlotwiseHealthTableEntry 3 }

//sync status OKAY==1 or FAIL==0"

snr OBJECT-TYPE
--OID .1.3.6.1.4.1.21025.4.4.9.1.4	
    SYNTAX      Integer32
    MAX-ACCESS  read-only
    STATUS      current
    DESCRIPTION
        "SNR of each slot"
    ::= { SlotwiseHealthTableEntry 4 }
//15-27

indexhealth OBJECT-TYPE
--OID .1.3.6.1.4.1.21025.4.4.9.1.5	
    SYNTAX      Integer32
    MAX-ACCESS  read-only
    STATUS      current
    DESCRIPTION
        "index of slotwise health table"
    ::= { SlotwiseHealthTableEntry 5 }


-- Variables under lcpIpAddrConfigure

managerIpaddress OBJECT-TYPE
--OID .1.3.6.1.4.1.21025.4.6.3	
    SYNTAX     IpAddress
    MAX-ACCESS read-only
    STATUS     current
    DESCRIPTION
            " Management port IPaddress"
    ::= { lcpIpAddrConfigure 3}

nmaddr OBJECT-TYPE
--OID .1.3.6.1.4.1.21025.4.6.4	
    SYNTAX     IpAddress
    MAX-ACCESS read-only
    STATUS     current
    DESCRIPTION
            " Management port Netmask address"
    ::= { lcpIpAddrConfigure 4}

-- Variables under lcpTraps

txpllLock  NOTIFICATION-TYPE
--OID .1.3.6.1.4.1.21025.4.7.1
    	STATUS      current
         DESCRIPTION
             "Emitted when txPLL unlocks"
    	::= { lcpTraps 1 }

rxpllLock  NOTIFICATION-TYPE
--OID .1.3.6.1.4.1.21025.4.7.2
    STATUS      current
    DESCRIPTION
            "rxPLL-lock status "
    ::= { lcpTraps 2 }

txLowPower  NOTIFICATION-TYPE
--OID .1.3.6.1.4.1.21025.4.7.3
    STATUS      current
    DESCRIPTION
            "Transmit power low notification "
    ::= { lcpTraps 3 }

syncLossSlt1  NOTIFICATION-TYPE
--OID .1.3.6.1.4.1.21025.4.7.4
    STATUS      current
    DESCRIPTION
            "Synchronization lost notification for slot1"
    ::= { lcpTraps 4 }

syncLossSlt2  NOTIFICATION-TYPE
--OID .1.3.6.1.4.1.21025.4.7.5
    STATUS      current
    DESCRIPTION
            "Synchronization lost notification for slot2"
    ::= { lcpTraps 5 }

syncLossSlt3  NOTIFICATION-TYPE
--OID .1.3.6.1.4.1.21025.4.7.6
    STATUS      current
    DESCRIPTION
            "Synchronization lost notification for slot3"
    ::= { lcpTraps 6 }

syncLossSlt4  NOTIFICATION-TYPE
--OID .1.3.6.1.4.1.21025.4.7.7
    STATUS      current
    DESCRIPTION
            "Synchronization lost notification for slot4"
    ::= { lcpTraps 7 }

syncLossSlt5  NOTIFICATION-TYPE
--OID .1.3.6.1.4.1.21025.4.7.8
    STATUS      current
    DESCRIPTION
            "Synchronization lost notification for slot5"
    ::= { lcpTraps 8 }

syncLossSlt9  NOTIFICATION-TYPE
--OID .1.3.6.1.4.1.21025.4.7.9
    STATUS      current
    DESCRIPTION
            "Synchronization lost notification for slot6"
    ::= { lcpTraps 9 }

sysVoltagesOutOfLimitminus5V  NOTIFICATION-TYPE
--OID .1.3.6.1.4.1.21025.4.7.30
    STATUS      current
    DESCRIPTION
            "abnormal voltages minus 5V "
    ::= { lcpTraps 30 }

sysVoltagesOutOfLimitplu5V  NOTIFICATION-TYPE
--OID .1.3.6.1.4.1.21025.4.7.31
    STATUS      current
    DESCRIPTION
            "abnormal voltages plus 5V "
    ::= { lcpTraps 31 }

sysVoltagesOutOfLimitplus30V  NOTIFICATION-TYPE
--OID .1.3.6.1.4.1.21025.4.7.32
    STATUS      current
    DESCRIPTION
            "abnormal voltages plus 30V "
    ::= { lcpTraps 32 }

sysVoltagesOutOfLimitplus49V  NOTIFICATION-TYPE
--OID .1.3.6.1.4.1.21025.4.7.34
    STATUS      current
    DESCRIPTION
            "abnormal voltages plus 49V "
    ::= { lcpTraps 34 }

END
//All notifications response 0/1;
